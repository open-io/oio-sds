GRIDSTORAGE-MIB DEFINITIONS ::= BEGIN

IMPORTS
    MODULE-IDENTITY, OBJECT-TYPE, Integer32,
    enterprises, Counter32         FROM SNMPv2-SMI
    TEXTUAL-CONVENTION             FROM SNMPv2-TC;

atosOrigin MODULE-IDENTITY
    LAST-UPDATED "200801070000Z"
    ORGANIZATION "Atos WorldLine"
    CONTACT-INFO "Technical Operations
                  Atos WorldLine
                  Rue de la Pointe - ZI A
                  59113 SECLIN
                  FRANCE"
    DESCRIPTION  "The MIB module to describe GridStorage objects."
    REVISION     "200801070000Z"
    DESCRIPTION  "Initial v2 version of this MIB module."
    ::= { enterprises 3629 }

gridStorage OBJECT IDENTIFIER ::= { atosOrigin 66 }


-- Meta0 objects definitions
meta0 OBJECT IDENTIFIER ::= { gridStorage 0 }

-- Meta0Index contains the semantics of ifIndex and should be used
-- for any objects defined in other MIB modules that need these semantics.
Meta0Index ::= TEXTUAL-CONVENTION
    DISPLAY-HINT "d"
    STATUS       current
    DESCRIPTION
            "A unique value, greater than zero, for each meta0."
    SYNTAX       Integer32 (1..2147483647)

m0Number OBJECT-TYPE
    SYNTAX       Integer32
    MAX-ACCESS   read-only
    STATUS       current
    DESCRIPTION
            "The number of meta0 running on this system."
    ::= { meta0 1 }

-- The meta0 table
m0Table OBJECT-TYPE
    SYNTAX      SEQUENCE OF M0Entry
    MAX-ACCESS  not-accessible
    STATUS      current
    DESCRIPTION
            "A list of meta0 entries. The number of entries is
             given by the value of m0Number."
    ::= { meta0 2 }

m0Entry OBJECT-TYPE
    SYNTAX     M0Entry
    MAX-ACCESS not-accessible
    STATUS     current
    DESCRIPTION
            "An entry containing management information applicable to a
             particular meta0."
    INDEX   { m0Index }
    ::= { m0Table 1 }

M0Entry ::=
    SEQUENCE {
        m0Index            Meta0Index,
        m0Req              Counter32
    }

m0Index OBJECT-TYPE
    SYNTAX     Meta0Index
    MAX-ACCESS read-only
    STATUS     current
    DESCRIPTION
            "A unique value, greater than zero, for each meta0. It
             is recommended that values are assigned contiguously
             starting from 1."
    ::= { m0Entry 1 }

m0Req OBJECT-TYPE
    SYNTAX     Counter32
    MAX-ACCESS read-only
    STATUS     current
    DESCRIPTION
            "The total number of requests executed by the meta0."
    ::= { m0Entry 2 }


-- Meta1 objects definitions
meta1 OBJECT IDENTIFIER ::= { gridStorage 1 }

-- Meta1Index contains the semantics of ifIndex and should be used
-- for any objects defined in other MIB modules that need these semantics.
Meta1Index ::= TEXTUAL-CONVENTION
    DISPLAY-HINT "d"
    STATUS       current
    DESCRIPTION
            "A unique value, greater than zero, for each meta1."
    SYNTAX       Integer32 (1..2147483647)

m1Number OBJECT-TYPE
    SYNTAX       Integer32
    MAX-ACCESS   read-only
    STATUS       current
    DESCRIPTION
            "The number of meta1 running on this system."
    ::= { meta1 1 }

-- The meta1 table
m1Table OBJECT-TYPE
    SYNTAX      SEQUENCE OF M1Entry
    MAX-ACCESS  not-accessible
    STATUS      current
    DESCRIPTION
            "A list of meta1 entries. The number of entries is
             given by the value of m1Number."
    ::= { meta1 2 }

m1Entry OBJECT-TYPE
    SYNTAX     M1Entry
    MAX-ACCESS not-accessible
    STATUS     current
    DESCRIPTION
            "An entry containing management information applicable to a
             particular meta1."
    INDEX   { m1Index }
    ::= { m1Table 1 }

M1Entry ::=
    SEQUENCE {
        m1Index            Meta1Index,
        m1Req              Counter32
    }

m1Index OBJECT-TYPE
    SYNTAX     Meta1Index
    MAX-ACCESS read-only
    STATUS     current
    DESCRIPTION
            "A unique value, greater than zero, for each meta1. It
             is recommended that values are assigned contiguously
             starting from 1."
    ::= { m1Entry 1 }

m1Req OBJECT-TYPE
    SYNTAX     Counter32
    MAX-ACCESS read-only
    STATUS     current
    DESCRIPTION
            "The total number of requests executed by the meta1."
    ::= { m1Entry 2 }


-- Meta2 objects definitions
meta2 OBJECT IDENTIFIER ::= { gridStorage 2 }

-- Meta2Index contains the semantics of ifIndex and should be used
-- for any objects defined in other MIB modules that need these semantics.
Meta2Index ::= TEXTUAL-CONVENTION
    DISPLAY-HINT "d"
    STATUS       current
    DESCRIPTION
            "A unique value, greater than zero, for each meta2."
    SYNTAX       Integer32 (1..2147483647)

m2Number OBJECT-TYPE
    SYNTAX       Integer32
    MAX-ACCESS   read-only
    STATUS       current
    DESCRIPTION
            "The number of meta2 running on this system."
    ::= { meta2 1 }

-- The meta2 table
m2Table OBJECT-TYPE
    SYNTAX      SEQUENCE OF M2Entry
    MAX-ACCESS  not-accessible
    STATUS      current
    DESCRIPTION
            "A list of meta2 entries. The number of entries is
             given by the value of m2Number."
    ::= { meta2 2 }

m2Entry OBJECT-TYPE
    SYNTAX     M2Entry
    MAX-ACCESS not-accessible
    STATUS     current
    DESCRIPTION
            "An entry containing management information applicable to a
             particular meta2."
    INDEX   { m2Index }
    ::= { m2Table 1 }

M2Entry ::=
    SEQUENCE {
	m2Index            Meta2Index,
	m2Desc             DisplayString,
        m2Req              Counter32
    }

m2Index OBJECT-TYPE
    SYNTAX     Meta2Index
    MAX-ACCESS read-only
    STATUS     current
    DESCRIPTION
            "A unique value, greater than zero, for each meta2. It
             is recommended that values are assigned contiguously
             starting from 1."
    ::= { m2Entry 1 }

m2Desc OBJECT-TYPE
    SYNTAX     DisplayString
    MAX-ACCESS read-only
    STATUS     current
    DESCRIPTION
            "The meta2 description string."
    ::= { m2Entry 2 }

m2Req OBJECT-TYPE
    SYNTAX     Counter32
    MAX-ACCESS read-only
    STATUS     current
    DESCRIPTION
            "The total number of requests recieved by the meta2."
    ::= { m2Entry 3 }


END
