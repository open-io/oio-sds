AWL-MetaDirectory-Protocol DEFINITIONS AUTOMATIC TAGS ::=
BEGIN
	RowField ::= SEQUENCE {
		pos INTEGER,
		-- value OCTET STRING OPTIONAL
		value CHOICE {
			i INTEGER,
			f REAL,
			b OCTET STRING,
			s PrintableString
		}
	}

	Row ::= SEQUENCE {
		rowid INTEGER,
		fields SEQUENCE OF RowField OPTIONAL
	}

	RowName ::= SEQUENCE {
		pos INTEGER,
		name OCTET STRING
	}

	Table ::= SEQUENCE {
		name OCTET STRING,
		header SEQUENCE OF RowName,
		rows SEQUENCE OF Row
	}

	TableSequence ::= SEQUENCE OF Table

	TableVersion ::= SEQUENCE {
		name PrintableString,
		version INTEGER,
		when INTEGER
	}

	BaseVersion ::= SEQUENCE OF TableVersion
END
